module shashankp {
    yang-version 1.1;
    namespace "urn:opendaylight:params:xml:ns:yang:shashankp";
    prefix "shashankp";

    revision "2017-08-30" { // TODO change revision to date of model creation
        description "Initial revision of shashankp model";
    }
}
